(defun c:unigen(/ p1 dataF conecVol conecData firstPoint)
	(setq p1 (getpoint "\nPrimer punto"))
	(command "osmode" 0)
	(Layers)
	(setq dataF (data))
	(foreach orden dataF
		(if (= firstPoint nil)
			(setq firstPoint p1)
			(setq p1 (list (DesfasarCaja (car conecVol) (caddr orden)) (cadr (car conecVol))))
		)
		(setq conecVol (general p1 (caddr orden) (car orden) (cadr orden)))
		(if (/= (cadr conecVol) nil)
			(if (= conecData nil)
				(setq conecData (cadr conecVol))
				(setq conecData (append conecData (cadr conecVol)))
			)
		)
	)
	(conexiones conecData)
	(if (/= (cData) nil)
		(condensadores firstPoint (caddr (car dataF)))
	)
	(if (/= (eData) nil)
		(electrogeno conecData)
	)
)
